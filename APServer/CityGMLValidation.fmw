FME workspace CityGMLValidation.fmw

Parameters:
- ADE_XSD_DOC =
- BOUNDEDBY =
- COORD =
- INPUT =
- LOG_FILE =
- OUTPUT =
- OVERLAP =
- OVER_CHECK =
- PLAN_ANG =
- PLAN_DIST =
- PREC =
- SRS_AXIS =
- TOLERANCE =

Readers:
- CITYGML_1: CITYGML from $(INPUT)

Note: CityGML data input. / All data are currently read into FME / During the import if textures are present then these will be applied to surfaces. It is recommeneded that the textures folder be renamed (or moved) prior to processing to improve performance. / Upon read any features which are missing gml:id's will be given a UUID with an 'fme' prefix.
WallSurface (reader CITYGML_1)
    attributes: citygml_level_of_detail{} xml_char(200), citygml_feature_role xml_char(200)
    -> AppearanceRemover_8
Note: Remove any appearences to reduce memory requirements
AppearanceRemover_8
    SIDE_TO_REMOVE = Front and Back Sides
    -> Tester_16
    UNMATCHED -> Tester_16
    <REJECTED> -> Tester_16
Note: Drop CityModel and CityObjectGroup placeholders
Note: Reproject to valid coordinate system. / The units will be checked. Only meters are supported. / Chosen coordinate systems which are not in meters will cause the process to fail / A projected coordiante system is required for geomerty tests.
Tester_16
    BOOL_OP = OR
    COMPOSITE_TEST = 1 OR 2
    TEST_CLAUSE:
      TEST @Value(fme_feature_type) = CityModel
      TEST @Value(fme_feature_type) = CityObjectGroup
    TEST_MODE = TEST
    FAILED -> AttributeKeeper_10
AttributeKeeper_10
    CREATE_BULK_MODE_FEATURES = No
    KEEP_ATTRS = citygml_feature_role,fme_dataset,fme_feature_type,gml_id,gml_parent_id,fme_rejection_code
    KEEP_LIST = citygml_level_of_detail{}
    -> CsmapReprojector
Note: Only Unique features (based on gmlid) will get properly validated
DuplicateFilter
    INPUT_ORDERED_CHOICE = No
    KEYATTR = gml_id
    UNIQUE -> AttributeKeeper_4
    UNIQUE -> Junction_6
    DUPLICATE -> Junction_4
Note: Multiple Geoemtries are split into seperate features. This helps ensure that all primitives are in the same realtive structure.
Junction_6
    -> MultipleGeometryFilter
    -> AttributeKeeper
Note: Collect Buidlings Bridges and tunnel componets into heirachy. / Features which are not part of these are output via the rejected port. Keeping the features aggregated by top level city objects helps to make the results clearer and allows for easier extraction of parts to test.
CityGMLBuildingBridgeCollector: CityGMLBuildingCollector
    FME_FEATURE_TYPE = @Value(fme_feature_type)
    GML_ID = @Value(gml_id)
    GML_PARENT_ID = @Value(gml_parent_id)
    Rejected -> GeometryPartExtractor_3
    Rejected -> AttributeKeeper_6
    Aggregated -> GeometryPropertyExtractor_7
    Aggregated -> AttributeKeeper_6
Note: extract lod_name so we can test for lod2 even if geoemtry is null
GeometryPropertyExtractor_7
    EXTRACTTYPE_PARAM = Geometry Name
    GEOM_NAME_FIELD = _lod_name
    GQUERY:
      for $geom in //geometry
      where (fme:trait-equals(fme:get-trait($geom, 'type'), 'Building')
      or fme:trait-equals(fme:get-trait($geom, 'type'), 'BuildingPart'))
      and (fme:trait-equals(fme:get-trait($geom, 'citygml_feature_role'), 'cityObjectMember')
      or fme:trait-equals(fme:get-trait($geom, 'citygml_feature_role'), 'consistsOfBuildingPart'))
      return number($geom/@fme_id)
    EXTRACTED -> GeometryPartExtractor_3
    UNMATCHED -> GeometryPartExtractor_3
    UNTOUCHED -> GeometryPartExtractor_3
Note: Extract SolidPrimitives. Extracted Solids are passed on towards geometry validation. / Untouched and Remaining geometries are fed towards the Bounding Surface check
Note: MULTI SURFACE CHECK CAN BE STARTED HERE
GeometryPartExtractor_3
    GQUERY:
      for $geom in //geometry
      where $geom/@fme_geometry_type = 'IFMEBRepSolid'
      or $geom/@fme_geometry_type = 'IFMECompositeSolid'
      return number($geom/@fme_id)
    EXTRACTED -> GeometryPropertyRenamer
    REMAINING -> Tester_3
    UNTOUCHED -> Tester_3
    UNTOUCHED -> Tester_5
Note: Check user input
Note: Check for walls, ground, roof surfaces from LoD2(3) Building and Building Parts
Tester_3
    BOOL_OP = OR
    COMPOSITE_TEST = 1
    TEST_CLAUSE = TEST $(BOUNDEDBY) = Yes
    TEST_MODE = TEST
    PASSED -> DuplicateFilter_11
Junction_2
    -> GeometryValidator_4
    -> GeometryPropertyExtractor_5
Note: Identify lod2Solids without xlinked surfaces
GeometryPropertyExtractor_5
    EXTRACTTYPE_PARAM = Geometry Name
    GEOM_NAME_FIELD = _geometry_name
    GQUERY:
      for $geom in //geometry
      where <fme-in-operation>fme:trait-equals(fme:get-trait($geom/ancestor::geometry, 'citygml_lod_name'), 'lod2Solid')</fme-in-operation>
      and $geom/@fme_geometry_name = 'surfaceMember'
      and fme:get-trait-property($geom, 'xlink_href', $fme:ISMISSING)
      return number($geom/@fme_id)
    EXTRACTED -> GeometryPartExtractor
    EXTRACTED -> GeometryRemover_4
    UNMATCHED -> GeometryPropertyExtractor_6
AttributeKeeper_6
    CREATE_BULK_MODE_FEATURES = NO
    KEEP_ATTRS = gml_id,fme_feature_type,type,fme_dataset
    KEEP_LIST = citygml_level_of_detail{}
    -> TestFilter
TestFilter
    DEFAULT_VALUE = <UNFILTERED>
    TEST_LIST:
      "BOOL_OP,COMPOSITE,COMPOSITE_TEST,""""""1 AND 2"""""",TEST_CLAUSE,TEST @Value(type) = Building
      TEST $(OVER_CHECK) = LoD1",LoD1,"BOOL_OP,AND,COMPOSITE_TEST,""""""1 AND 2"""""",TEST_CLAUSE,TEST @Value(type) = Building
      TEST $(OVER_CHECK) = LoD2",LoD2,"BOOL_OP,AND,COMPOSITE_TEST,""""""1 AND 2"""""",TEST_CLAUSE,TEST @Value(type) = Building
      TEST $(OVER_CHECK) = LoD3",LoD3,"BOOL_OP,AND,COMPOSITE_TEST,""""""1 AND 2"""""",TEST_CLAUSE,TEST @Value(type) = Building
      TEST $(OVER_CHECK) = ALL",ALL
    LoD1 -> ListConcatenator
    LoD2 -> ListConcatenator_2
    LoD3 -> ListConcatenator_3
    ALL -> OverlapPercentCalculator_2
ListConcatenator
    DROP_EMPTY_PARTS = No
    LIST_ATTR = citygml_level_of_detail{}
    SEP = ,
    VAL_ATTR = lods
    -> Tester_6
Tester_6
    BOOL_OP = OR
    COMPOSITE_TEST = 1
    TEST_CLAUSE = CASE_INSENSITIVE_TEST @Value(lods) CONTAINS 1
    TEST_MODE = TEST
    PASSED -> Junction_8
ListConcatenator_2
    DROP_EMPTY_PARTS = No
    LIST_ATTR = citygml_level_of_detail{}
    SEP = ,
    VAL_ATTR = lods
    -> Tester_10
Tester_10
    BOOL_OP = OR
    COMPOSITE_TEST = 1
    TEST_CLAUSE = CASE_INSENSITIVE_TEST @Value(lods) CONTAINS 2
    TEST_MODE = CASE_INSENSITIVE_TEST
    PASSED -> Junction_8
ListConcatenator_3
    DROP_EMPTY_PARTS = No
    LIST_ATTR = citygml_level_of_detail{}
    SEP = ,
    VAL_ATTR = lods
    -> Tester_12
Tester_12
    BOOL_OP = OR
    COMPOSITE_TEST = 1
    TEST_CLAUSE = CASE_INSENSITIVE_TEST @Value(lods) NOT_CONTAINS 3
    TEST_MODE = CASE_INSENSITIVE_TEST
    PASSED -> Junction_8
Junction_8
    -> OverlapPercentCalculator_2
Note: Overlap calculation is performed in here. Data are forced into 2D and dissolved into a single 2D feature per building. It is assumed here that a Building feature will not be disjoint from itself. / This may need to be modified to check for that.
OverlapPercentCalculator_2
    ID = @Value(gml_id)
    OVERLAP = $(OVERLAP)
    SHOW_OVERLAPS = Yes
    FAIL -> AttributeCreator_8
    PASS -> Junction_3
    NO_OVERLAP -> Junction_3
Note: ERROR 614
AttributeCreator_8
    ATTR_TABLE:
      SET_TO error_code = 614
      SET_TO error_level = FAIL
    -> Junction_3
Note: Thes junction should contain all top level city objects. Data here passes to the output. It is the only place where valid 'features' make it to the output report
Junction_3
    -> Junction
Note: Parse ADE file paths - The purpose of this area is simply to parse the ADE file paths for the sumary report. This can be removed if this is not needed (or wanted) in the report
FeatureWriter
    DATASET = @Value(_dirpath)\@Value(_folder)\@Value(_filename)
    DATASET_ATTR = _dataset
    FEATURE_TYPE_LIST_ATTR = _feature_type
    FORMAT = TEXTLINE
    TEXTLINE_COORDINATE_SYSTEM_GRANULARITY = FEATURE
    TEXTLINE_DESTINATION_DATASETTYPE_VALIDATION = Yes
    TEXTLINE_ENCODING = UTF-8
    TEXTLINE_END_OF_LINE = System
    TEXTLINE_MIME_TYPE = text/plain
    TEXTLINE_OVERWRITE_FILE = YES
    TEXTLINE_WRITE_LAST_EOL = YES
    TEXTLINE_WRITE_UTF8_BOM = YES
    TOTAL_FEATURES_WRITTEN_ATTR = _total_features_written

Bookmark: Reproject to valid coordinate system
CsmapReprojector
    DEST = $(COORD)
    INTERPOLATION_TYPE_NAME = Nearest Neighbor
    RASTER_CELL_SIZE = Preserve Cells
    RASTER_TOLERANCE = 0.0
    VERTICAL_HANDLING = Ignore heights and leave them unchanged
    REPROJECTED -> CoordinateSystemMapUnitExtractor
CoordinateSystemMapUnitExtractor
    -> Tester_2
Tester_2
    BOOL_OP = OR
    COMPOSITE_TEST = 1
    TEST_CLAUSE = TEST @Value(_units) = m
    TEST_MODE = TEST
    PASSED -> DuplicateFilter
    FAILED -> Terminator
Terminator
    MESSAGE = Selected CoordinateSystem units are not in meters

Bookmark: Check for duplicate gml_id's for each feature
Note: Collect Duplicates
Junction_4
    -> AttributeKeeper_3
AttributeKeeper_3
    CREATE_BULK_MODE_FEATURES = No
    KEEP_ATTRS = fme_dataset,fme_feature_type,gml_id
    -> GeometryRemover_5
GeometryRemover_5
    -> FeatureMerger_3 [REQUESTOR]
AttributeKeeper_4
    CREATE_BULK_MODE_FEATURES = No
    KEEP_ATTRS = fme_dataset,fme_feature_type,gml_id
    -> GeometryRemover_6
GeometryRemover_6
    -> FeatureMerger_3 [SUPPLIER]
FeatureMerger_3
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(gml_id) @Value(gml_id) AUTO
    MERGE_TYPE = Attributes Only
    PROCESS_DUPS = YES
    REJECT_NULL_MISSING_KEYS = No
    SUPPLIERS_FIRST = No
    MERGED -> AttributeCreator
    USED_SUPPLIER -> AttributeCreator
Note: ERROR 905
AttributeCreator
    ATTR_TABLE:
      SET_TO error_code = 905
      SET_TO error_level = FAIL
    -> Sampler_5
Sampler_5
    GROUP_BY = fme_dataset error_code
    RATE = 1
    SAMPLE_MODE = No
    SAMPLE_TYPE_LONG = First N Features
    SAMPLED -> Sorter
    SAMPLED -> Junction_5
    NOT_SAMPLED -> Sorter
Sorter
    SORT_PARM = gml_id ALPHA ASCENDING
    SORTED -> JSONTemplater [DATASET]

Bookmark: Xlinks checks - xlink surfaces are extracted from solids and their gml:id's are compared to bounding surfaces to see if there is a match. This is fairly intesntive. Future releases could see this test being optional
AttributeKeeper
    CREATE_BULK_MODE_FEATURES = No
    KEEP_ATTRS = citygml_feature_role,fme_dataset,fme_feature_type,gml_id,gml_parent_id
    -> Tester_4
GeometryPartExtractor_2
    GQUERY:
      for $geom in //geometry
      where ($geom/@fme_geometry_type = 'IFMEFace'
      or $geom/@fme_geometry_type = 'IFMECompositeSurface')
      and fme:get-trait-property($geom, 'gml_id', $fme:HASAVALUE)
      return number($geom/@fme_id)
    EXTRACTED -> GeometryPropertyRenamer_2
GeometryPropertyRenamer_2
    GQUERY:
      for $geom in //geometry
      where fme:get-trait-property($geom, 'gml_id', $fme:HASAVALUE)
      return number($geom/@fme_id)
    PARAM_LIST = gml_id,geom_gml_id
    RENAMETYPE_PARAM = Traits
    RENAMED -> GeometryPropertyExtractor_4
GeometryPropertyExtractor_4
    EXTRACTTYPE_PARAM = Traits
    GQUERY:
      for $geom in //geometry
      where fme:get-trait-property($geom, 'geom_gml_id', $fme:HASAVALUE)
      and $geom/@fme_geometry_type = 'IFMEFace'
      return number($geom/@fme_id)
    PREFIX_EXTRACTED_TRAITS = No
    TRAIT_ATTR_LIST = geom_gml_id,No
    EXTRACTED -> GeometryRemover_2
GeometryRemover_2
    -> AttributeKeeper_8
AttributeKeeper_8
    CREATE_BULK_MODE_FEATURES = No
    KEEP_ATTRS = citygml_feature_role,fme_feature_type,gml_id,gml_parent_id,fme_dataset,geom_gml_id
    -> FeatureJoiner [RIGHT]
Note: Identify lod3Solids without xlinked surfaces
GeometryPropertyExtractor_6
    EXTRACTTYPE_PARAM = Geometry Name
    GEOM_NAME_FIELD = _geometry_name
    GQUERY:
      for $geom in //geometry
      where <fme-in-operation>fme:trait-equals(fme:get-trait($geom/ancestor::geometry, 'citygml_lod_name'), 'lod3Solid')</fme-in-operation>
      and $geom/@fme_geometry_name = 'surfaceMember'
      and fme:get-trait-property($geom, 'xlink_href', $fme:ISMISSING)
      return number($geom/@fme_id)
    EXTRACTED -> GeometryPartExtractor
    EXTRACTED -> GeometryRemover_4
    UNMATCHED -> GeometryPartExtractor
GeometryRemover_4
    -> AttributeCreator_16
Note: ERROR 617
AttributeCreator_16
    ATTR_TABLE:
      SET_TO error_code = 617
      SET_TO error_level = FAIL
    -> GeometryRemover_7
Note: Extract xlinked surfaces from lod2Solids
GeometryPartExtractor
    GQUERY:
      for $geom in //geometry
      where $geom/ancestor::geometry/@fme_geometry_type = 'IFMEBRepSolid'
      and $geom/ancestor::geometry/@fme_geometry_name = 'lod2Solid'
      and fme:get-trait-property($geom, 'xlink_href', $fme:HASAVALUE)
      return number($geom/@fme_id)
    EXTRACTED -> GeometryPropertyExtractor_2
    REMAINING -> GeometryPartExtractor_4
    UNTOUCHED -> GeometryPartExtractor_4
Note: Extract xlinked surfaces from lod3Solids
GeometryPartExtractor_4
    GQUERY:
      for $geom in //geometry
      where $geom/ancestor::geometry/@fme_geometry_type = 'IFMEBRepSolid'
      and $geom/ancestor::geometry/@fme_geometry_name = 'lod3Solid'
      and fme:get-trait-property($geom, 'xlink_href', $fme:HASAVALUE)
      return number($geom/@fme_id)
    EXTRACTED -> GeometryPropertyExtractor_2
GeometryPropertyExtractor_2
    EXTRACTTYPE_PARAM = Traits
    GQUERY:
      for $geom in //geometry
      where fme:get-trait-property($geom, 'xlink_href', $fme:HASAVALUE)
      and $geom/@fme_geometry_type = 'IFMEFace'
      return number($geom/@fme_id)
    PREFIX_EXTRACTED_TRAITS = No
    TRAIT_ATTR_LIST = xlink_href,No
    EXTRACTED -> StringReplacer
StringReplacer
    CASE = NO
    FIND_TEXT = #
    NO_MATCH = _FME_NO_OP_
    REGEXP = NO
    SRC_ATTRS = xlink_href
    -> GeometryRemover
GeometryRemover
    -> AttributeKeeper_2
AttributeKeeper_2
    CREATE_BULK_MODE_FEATURES = No
    KEEP_ATTRS = citygml_feature_role,citygml_lod_name,fme_feature_type,gml_geometry,gml_id,gml_parent_id,primitive_id,primitive_type,type,xlink_href,fme_dataset
    -> FeatureJoiner [LEFT]
Note: Join xlinks with resonable surfaces
FeatureJoiner
    ATTR_CONFLICT_RES = Use Left
    GEOMETRY_HANDLING = Use Left
    GROUP_BY = fme_dataset
    JOIN_KEYS = xlink_href geom_gml_id AUTO
    JOIN_MODE = Inner
    UNJOINED_LEFT -> AttributeCreator_17
Note: ERROR 619
AttributeCreator_17
    ATTR_TABLE:
      SET_TO error_code = 619
      SET_TO error_level = FAIL
    -> GeometryRemover_7

Bookmark: Extract resolable surfaces for xlinks
Tester_4
    BOOL_OP = OR
    COMPOSITE_TEST = 1
    TEST_CLAUSE = TEST @Value(citygml_feature_role) = boundedBy
    TEST_MODE = TEST
    PASSED -> GeometryPartExtractor_2

Bookmark: Split Multiple Geometries
MultipleGeometryFilter
    CONTAINS -> Deaggregator
    NOT_CONTAINS -> CityGMLBuildingBridgeCollector
    <REJECTED> -> CityGMLBuildingBridgeCollector
Deaggregator
    ATTR_ACCUM_MODE = Merge List Attributes
    ATTR_CONFLICT_RES = Use List Attribute Values
    EXPLODE_INSTANCES = No
    LIST_ATTR_MODE_LOOKUP = LEAN
    MODE = Flatten One Level
    SPLIT_COMPOSITES = No
    DEAGGREGATED -> CityGMLBuildingBridgeCollector

Bookmark: Check for walls, ground, roof LoD2(LoD3) Solids
DuplicateFilter_11
    INPUT_ORDERED_CHOICE = No
    KEYATTR = gml_id
    UNIQUE -> Tester_19
Tester_19
    BOOL_OP = COMPOSITE
    COMPOSITE_TEST = 1 OR 2 AND 3
    TEST_CLAUSE:
      TEST @Value(fme_feature_type) = Building
      TEST @Value(fme_feature_type) = BuildingPart
      CASE_INSENSITIVE_TEST @Value(_lod_name) CONTAINS 2
    TEST_MODE = PER_TEST
    PASSED -> GeometryPropertyExtractor_3
    FAILED -> Tester_11
Tester_11
    BOOL_OP = COMPOSITE
    COMPOSITE_TEST = 1 OR 2 AND 3
    TEST_CLAUSE:
      TEST @Value(fme_feature_type) = Building
      TEST @Value(fme_feature_type) = BuildingPart
      CASE_INSENSITIVE_TEST @Value(_lod_name) CONTAINS 3
    TEST_MODE = PER_TEST
    PASSED -> GeometryPropertyExtractor_3
    FAILED -> AttributeExposer_12
AttributeExposer_12
    ATTR_LIST = _lod_name{}
    -> ListSearcher_6
ListSearcher_6
    ATTR_VALUE = 2
    LIST_ATTR = _lod_name{}
    MATCHTYPE = REGULAR_EXPRESSION_ENCODED
    FOUND -> GeometryPropertyExtractor_3
    NOT_FOUND -> ListSearcher_4
ListSearcher_4
    ATTR_VALUE = 3
    LIST_ATTR = _lod_name{}
    MATCHTYPE = REGULAR_EXPRESSION_ENCODED
    FOUND -> GeometryPropertyExtractor_3
GeometryPropertyExtractor_3
    EXTRACTTYPE_PARAM = Traits
    GQUERY:
      for $geom in //geometry
      where $geom[count(child::geometry) > 0]/count(parent::geometry) > 0
      or $geom/@fme_geometry_type != 'IFMENull'
      return number($geom/@fme_id)
    PREFIX_EXTRACTED_TRAITS = No
    TRAIT_ATTR_LIST = citygml_level_of_detail,Yes
    EXTRACTED -> ListDuplicateRemover_4
    UNMATCHED -> GeometryPartExtractor_5
ListDuplicateRemover_4
    SRC_LIST = citygml_level_of_detail{}
    -> ListSearcher_5
ListSearcher_5
    ATTR_VALUE = 2
    LIST_ATTR = citygml_level_of_detail{}
    MATCHTYPE = FIRST_MATCHED_ENCODED
    FOUND -> GeometryPartExtractor_5
    NOT_FOUND -> ListSearcher_7
ListSearcher_7
    ATTR_VALUE = 3
    LIST_ATTR = citygml_level_of_detail{}
    MATCHTYPE = FIRST_MATCHED_ENCODED
    FOUND -> GeometryPartExtractor_5
GeometryPartExtractor_5
    GQUERY:
      for $geom in //geometry
      where fme:trait-equals(fme:get-trait($geom, 'type'), 'WallSurface')
      return number($geom/@fme_id)
    REMAINING -> GeometryPartExtractor_6
    UNTOUCHED -> GeometryPartExtractor_6
    UNTOUCHED -> AttributeCreator_12
Note: ERROR 611
AttributeCreator_12
    ATTR_TABLE:
      SET_TO error_code = 611
      SET_TO error_level = FAIL
    -> GeometryRemover_10
GeometryRemover_10
    -> Junction
GeometryPartExtractor_6
    GQUERY:
      for $geom in //geometry
      where fme:trait-equals(fme:get-trait($geom, 'type'), 'GroundSurface')
      return number($geom/@fme_id)
    REMAINING -> GeometryPartExtractor_7
    UNTOUCHED -> GeometryPartExtractor_7
    UNTOUCHED -> GeometryRemover_11
GeometryRemover_11
    -> AttributeCreator_5
Note: ERROR 610
AttributeCreator_5
    ATTR_TABLE:
      SET_TO error_code = 610
      SET_TO error_level = FAIL
    -> Junction
GeometryPartExtractor_7
    GQUERY:
      for $geom in //geometry
      where fme:trait-equals(fme:get-trait($geom, 'type'), 'RoofSurface')
      return number($geom/@fme_id)
    UNTOUCHED -> GeometryRemover_12
GeometryRemover_12
    -> AttributeCreator_11
Note: ERROR 612
AttributeCreator_11
    ATTR_TABLE:
      SET_TO error_code = 612
      SET_TO error_level = FAIL
    -> Junction

Bookmark: If no solid is found and the feaute is a building we report an error
Tester_5
    BOOL_OP = OR
    COMPOSITE_TEST = 1
    TEST_CLAUSE = TEST @Value(type) = Building
    TEST_MODE = TEST
    PASSED -> AttributeCreator_9
Note: ERROR 609
AttributeCreator_9
    ATTR_TABLE:
      SET_TO error_code = 609
      SET_TO error_level = FAIL
    -> Junction

Bookmark: Extract properties of primitives before checking primities. This allows for aggregation at the end of the process
GeometryPropertyRenamer
    GQUERY:
      for $geom in //geometry
      where $geom/count(parent::geometry) = 0
      return number($geom/@fme_id)
    PARAM_LIST = gml_id,primitive_id
    RENAMETYPE_PARAM = Traits
    RENAMED -> GeometryPropertyExtractor_8
    UNTOUCHED -> GeometryPropertyExtractor_8
GeometryPropertyExtractor_8
    EXTRACTTYPE_PARAM = Traits
    GQUERY:
      for $geom in //geometry
      where $geom/count(parent::geometry) = 0
      return number($geom/@fme_id)
    PREFIX_EXTRACTED_TRAITS = No
    TRAIT_ATTR_LIST = gml_geometry,No type,No citygml_lod_name,No primitive_id,No
    EXTRACTED -> AttributeCreator_3
AttributeCreator_3
    ATTR_TABLE = SET_TO primitive_type = @Value(gml_geometry)
    -> Tester_7
Tester_7
    BOOL_OP = OR
    COMPOSITE_TEST = 1
    TEST_CLAUSE = TEST primitive_id ATTRIBUTE_IS_MISSING ""
    TEST_MODE = TEST
    PASSED -> AttributeCreator_6
    FAILED -> Junction_2
Note: Add missing primitve id
AttributeCreator_6
    ATTR_TABLE = SET_TO primitive_id = MISSING_ID_@Count()
    -> Junction_2

Bookmark: PlanarChecks
GeometryValidator_4
    ISSUE_ATTR_NAME = _boundary_issues
    PRESETS = Custom
    REPAIR = No
    RULES = PLANAR_SURFACE CHECK_AREA]DO_NOT_CHECK_AREA]TOLERANCE_MODE]IGNORE]TOLERANCE]<Unused>]ANGULAR_TOLERANCE_MODE]CUSTOM]ANGULAR_TOLERANCE]$(PLAN_ANG)]FME_CONTROLLER_QUERY_FILE]transformers\dependencies\geometryvalidator\PLANAR_SURFACE.fme
    SUMMARY = Detailed
    PASSED -> GeometryValidator_5
    FAILED -> AttributeRemover_3
    FAILED -> AttributeCreator_13
GeometryValidator_5
    ISSUE_ATTR_NAME = _boundary_issues
    PRESETS = Custom
    REPAIR = No
    RULES = PLANAR_SURFACE CHECK_AREA]DO_NOT_CHECK_AREA]TOLERANCE_MODE]CUSTOM]TOLERANCE]$(PLAN_DIST)]ANGULAR_TOLERANCE_MODE]IGNORE]ANGULAR_TOLERANCE]<Unused>]FME_CONTROLLER_QUERY_FILE]transformers\dependencies\geometryvalidator\PLANAR_SURFACE.fme
    SUMMARY = Detailed
    PASSED -> GeometryValidator_3
    FAILED -> AttributeCreator_14
    FAILED -> AttributeRemover_4

Bookmark: GeometryTests
AttributeRemover_3
    LIST_ATTRS = _boundary_issues{}.count _boundary_issues{}.issue_found _boundary_issues{}.location_sample.x _boundary_issues{}.location_sample.y _boundary_issues{}.location_sample.z _boundary_issues{}.repair_state
    -> GeometryValidator_5
AttributeRemover_4
    LIST_ATTRS = _boundary_issues{}.count _boundary_issues{}.issue_found _boundary_issues{}.location_sample.x _boundary_issues{}.location_sample.y _boundary_issues{}.location_sample.z _boundary_issues{}.repair_state
    -> GeometryValidator_3
GeometryRemover_9
    -> Aggregator_4
    -> Junction
Note: ERROR 203
AttributeCreator_14
    ATTR_TABLE = SET_TO error_code = 203
    -> AttributeCreator_2
Note: ERROR 204
AttributeCreator_13
    ATTR_TABLE = SET_TO error_code = 204
    -> AttributeCreator_2
AttributeCreator_2
    ATTR_TABLE = SET_TO error_level = FAIL
    -> GeometryRemover_7
Note: Split geometry validation results results into individual features, extract details and map details to error code
GeometryRemover_7
    -> Junction
    -> Aggregator_4

Bookmark: Surface Checks
GeometryValidator_3
    ISSUE_ATTR_NAME = _boundary_issues
    PRESETS = Custom
    REPAIR = No
    RULES = NAN_REMOVAL PROCESS_MEASURE]NO]FME_CONTROLLER_QUERY_FILE]transformers\dependencies\geometryvalidator\NAN_REMOVAL.fme NULL_REMOVAL  CONSECUTIVE_IDENTICAL_VERTICES_2D CHECK_Z]YES]TOLERANCE]$(TOLERANCE)]FME_CONTROLLER_QUERY_FILE]transformers\dependencies\geometryvalidator\CONSECUTIVE_IDENTICAL_VERTICES_2D.fme AREA_ORIENTATION AREA_ORIENTATION]VALID]FME_CONTROLLER_QUERY_FILE]transformers\dependencies\geometryvalidator\AREA_ORIENTATION.fme SURFACE_ORIENTATION  SELF_INTERSECTING CHECK_HOLE_TOUCHING_POLYGON]No]CONNECT_Z_MODE_SI]FIRST_WINS]SELF_INTERSECTION_TOLERANCE]$(TOLERANCE)]FME_CONTROLLER_QUERY_FILE]transformers\dependencies\geometryvalidator\SELF_INTERSECTING.fme
    SUMMARY = Detailed
    PASSED -> CoordinateRounder
    FAILED -> AttributeKeeper_9
    FAILED -> AttributeRemover_2

Bookmark: Apply coordinate precision for solid watertight check
AttributeRemover_2
    LIST_ATTRS = _boundary_issues{} _boundary_issues{}.count _boundary_issues{}.issue_found _boundary_issues{}.location_sample.x _boundary_issues{}.location_sample.y _boundary_issues{}.location_sample.z _boundary_issues{}.repair_state
    -> CoordinateRounder
CoordinateRounder
    XPREC = $(PREC)
    YPREC = $(PREC)
    ZPREC = $(PREC)
    ROUNDED -> GeometryValidator_2
GeometryValidator_2
    PRESETS = Custom
    REPAIR = Yes
    RULES = CONSECUTIVE_IDENTICAL_VERTICES_2D CHECK_Z]YES]TOLERANCE]0]FME_CONTROLLER_QUERY_FILE]transformers/dependencies/geometryvalidator/CONSECUTIVE_IDENTICAL_VERTICES_2D.fme
    SUMMARY = None
    PASSED -> GeometryValidator_6
    FAILED -> GeometryValidator_6
    REPAIRED -> GeometryValidator_6

Bookmark: Solid Checks
GeometryValidator_6
    ISSUE_ATTR_NAME = _boundary_issues
    PRESETS = Custom
    REPAIR = No
    RULES = SHELL_VALIDATION FLIP_APPEARANCE_MODE]FLIP_APPEARANCES]FME_CONTROLLER_QUERY_FILE]transformers/dependencies/geometryvalidator/SHELL_VALIDATION.fme SOLID_VOID_REPAIR  SOLID_ORIENTATION
    SUMMARY = Detailed
    PASSED -> GeometryRemover_9
    FAILED -> AttributeKeeper_9

Bookmark: Split results into individual features
AttributeKeeper_9
    CREATE_BULK_MODE_FEATURES = NO
    KEEP_ATTRS = citygml_feature_role,citygml_lod_name,fme_dataset,fme_feature_type,gml_geometry,gml_id,gml_parent_id,primitive_id,primitive_type,type
    KEEP_LIST = _boundary_issues{} _boundary_issues{}.count _boundary_issues{}.issue_found _boundary_issues{}.location_sample.x _boundary_issues{}.location_sample.y _boundary_issues{}.location_sample.z _boundary_issues{}.repair_state
    -> GeometryRemover_8
GeometryRemover_8
    -> ListExploder_6
ListExploder_6
    ATTR_ACCUM_MODE = Merge List Attributes
    ATTR_CONFLICT_RES = Use List Attribute Values
    LIST_ATTR = _boundary_issues{}
    ELEMENTS -> AttributeExposer_6
AttributeExposer_6
    ATTR_LIST = supplementary_info{}
    -> ListExploder_7
ListExploder_7
    ATTR_ACCUM_MODE = Merge List Attributes
    ATTR_CONFLICT_RES = Use List Attribute Values
    LIST_ATTR = supplementary_info{}
    ELEMENTS -> AttributeExposer_7
AttributeExposer_7
    ATTR_LIST = details
    -> Tester
Tester
    BOOL_OP = OR
    COMPOSITE_TEST = 1
    TEST_CLAUSE = TEST @Value(details) = Miscellaneous
    TEST_MODE = TEST
    PASSED -> AttributeValueMapper_2
    FAILED -> AttributeValueMapper_5
AttributeValueMapper_2
    DEFAULT_VALUE = 999
    DIRECTION = Forward (Source To Destination)
    LUT = Building No Geoemtry,609,Contains NaNs or Infinities,100,Contains Null Geometry Parts,100,Degenerate or Corrupt Geometries,105,Duplicate Consecutive Points in 2D,102,Duplicate Consecutive Points in 3D,102,Duplicate Shells,402,Face Wrong Orientation,307,Feature Overlap,200,Incorrect Orientation,208,Incorrect Solid Orientation,405,Inner Shell Outside Outer,403,Interior of Shell Not Connected,404,Invalid Solid Boundaries,501,LoD2 Building No GroundSurface,610,LoD2 Building No RoofSurface,612,LoD2 Building No WallSurface,611,Multiple Connected Components,305,Not Enough Faces,301,Not Valid 2-Manifold,300,Not a Valid 2-Manifold,300,Self-Intersections in 2D,104,Shells Intersect,401,Surface Not Closed,302,Surface Self Intersects,306,Surface Wrong Orientation,308,Donut: Disjoint Interior,205,Unsupported LoD,613,Vertices Not Used,309,Donut: Overlapping Rings,201,Donut: Nested Hole,207,Donut: Hole Outside Shell,206,Donut: Touching Rings,201,Miscellaneous,999,Donut: Duplicate Rings,202,Contains -0, NaN, or Infinity,100
    SRC = issue_found
    VAL_ATTR = error_code
    -> AttributeCreator_2
Note: Other Geometry Erros
AttributeValueMapper_5
    DEFAULT_VALUE = 999
    DIRECTION = Forward (Source To Destination)
    LUT = Contains -0, NaN, or Infinity,100,Contains NaNs or Infinities,100,Contains Null Geometry Parts,100,Duplicate Consecutive Points in 2D,102,Duplicate Consecutive Points in 3D,102,Donut: Self-Intersection Error,104,Self-Intersections in 2D,104,Degenerate or Corrupt Geometries,105,Donut: Overlapping Rings,201,Donut: Touching Rings,201,Donut: Duplicate Rings,202,Donut: Disjoint Interior,205,Donut: Hole Outside Shell,206,Donut: Nested Hole,207,Incorrect Orientation,208,Not Valid 2-Manifold,300,Not a Valid 2-Manifold,300,Not Enough Faces,301,Surface Not Closed,302,Multiple Connected Components,305,Surface Self Intersects,306,Face Wrong Orientation,307,Surface Wrong Orientation,308,Vertices Not Used,309,Shells Intersect,401,Duplicate Shells,402,Inner Shell Outside Outer,403,Interior of Shell Not Connected,404,Incorrect Solid Orientation,405,Building No Geoemtry,609,LoD2 Building No GroundSurface,610,LoD2 Building No WallSurface,611,LoD2 Building No RoofSurface,612,Unsupported LoD,613,Miscellaneous,999
    SRC = details
    VAL_ATTR = error_code
    -> AttributeCreator_2

Bookmark: Collect Primitives
Note: Primitives
Aggregator_4
    ACCUM_ATTRS_NAME = Drop Incoming Attributes
    CONCAT_ATTRS = error_level
    GROUP_BY = primitive_id gml_id primitive_type type
    LIST_ATTRS_TO_INCLUDE = error_code error_level
    LIST_NAME = errors
    MODE = Attributes Only
    SEP = ,
    AGGREGATE -> Tester_9
    AGGREGATE -> DuplicateFilter_2
Tester_9
    BOOL_OP = OR
    COMPOSITE_TEST = 1
    TEST_CLAUSE = CASE_INSENSITIVE_TEST @Value(error_level) CONTAINS FAIL
    TEST_MODE = TEST
    PASSED -> AttributeCreator_7
AttributeCreator_7
    ATTR_TABLE = SET_TO validity = FME_CONDITIONAL:DEFAULT_VALUE'1'BOOL_OP;OR;COMPOSITE_TEST;1;CASE_INSENSITIVE_TEST @Value(error_level) CONTAINS FAIL'0'BOOL_OP;OR;COMPOSITE_TEST;1;CASE_INSENSITIVE_TEST @Value(error_level) CONTAINS WARNING'1'FME_NUM_CONDITIONS3___
    -> JSONTemplater [PRIMITIVES]
DuplicateFilter_2
    INPUT_ORDERED_CHOICE = No
    KEYATTR = primitive_id gml_id
    UNIQUE -> ListSearcher_2
ListSearcher_2
    ATTR_VALUE = FAIL
    LIST_ATTR = errors{}.error_level
    MATCHTYPE = FIRST_MATCHED_ENCODED
    FOUND -> Aggregator_7
    NOT_FOUND -> Aggregator_8
Aggregator_7
    ACCUM_ATTRS_NAME = Merge Incoming Attributes
    COUNT_ATTR = _prims_failed_count
    GROUP_BY = primitive_type type
    MODE = Attributes Only
    SEP = ,
    AGGREGATE -> Aggregator_6
Aggregator_8
    ACCUM_ATTRS_NAME = Merge Incoming Attributes
    COUNT_ATTR = _prims_passed_count
    GROUP_BY = primitive_type type
    MODE = Attributes Only
    SEP = ,
    AGGREGATE -> Aggregator_6
Aggregator_6
    ACCUM_ATTRS_NAME = Merge Incoming Attributes
    GROUP_BY = primitive_type type
    MODE = Attributes Only
    SEP = ,
    AGGREGATE -> AttributeCreator_15
AttributeCreator_15
    ATTR_TABLE:
      SET_TO _prims_passed_count = FME_CONDITIONAL:DEFAULT_VALUE'_FME_NO_OP_'BOOL_OP;OR;COMPOSITE_TEST;1;TEST _prims_passed_count ATTRIBUTE_IS_MISSING _FME_BLANK_STRING_'0'FME_NUM_CONDITIONS2___
      SET_TO _prims_failed_count = FME_CONDITIONAL:DEFAULT_VALUE'_FME_NO_OP_'BOOL_OP;OR;COMPOSITE_TEST;1;TEST _prims_failed_count ATTRIBUTE_IS_MISSING _FME_BLANK_STRING_'0'FME_NUM_CONDITIONS2___
    -> ExpressionEvaluator_3
ExpressionEvaluator_3
    ACTION = Create New Attribute
    EXPRESSION = @Value(_prims_failed_count)+@Value(_prims_passed_count)
    VAL_ATTR = _num_primitives
    -> AttributeKeeper_7
AttributeKeeper_7
    CREATE_BULK_MODE_FEATURES = No
    KEEP_ATTRS = _num_primitives,_prims_failed_count,_prims_passed_count,primitive_type,type
    -> JSONTemplater [PRIMSUM]

Bookmark: Structure Output - This is the area where all features
Note: Collect all Features and feature level errors
Junction
    -> Junction_5
    -> Aggregator
Junction_5
    -> FilenamePartExtractor
    -> Tester_32
ListSorter_4
    ORDER = Ascending
    SRC_LIST = errors{}.error_code
    TYPE = Alphabetic
    -> ListDuplicateRemover_6
Note: The JSONTemplater structures the input features into a nested JSON format. / Features and primitives are linked based on the gml:id.
Note: Build Report
JSONTemplater
    DATASET_QUERY_EXPR:
      {
          "error": xs:integer(fme:get-attribute("error_code")),
          "file_name": fme:get-attribute("fme_dataset"),
          "gml_id": fme:get-attribute("gml_id"),
          "type": fme:get-attribute("fme_feature_type")
      }
    ERRORS_QUERY_EXPR:
      {
          "error_code": xs:integer(fme:get-attribute("error_code")),
          "error_desc": fme:get-attribute("_description"),
          "count": xs:integer(fme:get-attribute("error_code.total_count"))
      }
    FEATSUM_QUERY_EXPR:
      {
           "type" : fme:get-attribute("fme_feature_type"),
           "features_tested" : fme:get-attribute("_num_cityobjects"),
           "invalid_count": fme:get-attribute("_failed_count")
      }
    FEATURES_QUERY_EXPR:
      {
        "id": fme:get-attribute("gml_id"),
        "type": fme:get-attribute("fme_feature_type"),
        "validity": xs:boolean(fme:get-attribute("validity")),
        "errors": [
          for $v in fme:get-list-attribute('errors{}.error_code')
          return xs:integer($v)
      ],
        "primitives": fme:process-features("PRIMITIVES", "gml_id", fme:get-attribute("gml_id"))
      }
    PRIMITIVES_QUERY_EXPR:
      {
        "id": fme:get-attribute("primitive_id"),
        "type": fme:get-attribute("primitive_type"),
        "validity": xs:boolean(fme:get-attribute("validity")),
        "errors": [
          for $v in fme:get-list-attribute('errors{}.error_code')
          return xs:integer($v)
      ]
      }
    PRIMSUM_QUERY_EXPR:
      {
        "citygml_type": fme:get-attribute("type"),
        "type": fme:get-attribute("primitive_type"),
        "primitives_tested": fme:get-attribute("_num_primitives"),
        "invalid_count": fme:get-attribute("_prims_failed_count")
      }
    RESULT_ATTRIBUTE = _result
    ROOT_QUERY_EXPR:
      {
        "all_errors": fme:process-features("ERRORS"),
        "input_file(s)": [(fme:get-list-attribute("fme_dataset{}.fme_dataset"))],
        "input_file_type": "CityGML",
        "note": "this process currently only checks geometry checks on solid primitives, other primitive types are skipped",
          "parameters": {
          "ADE_schema(s)": fme:get-list-attribute('_xsd{}._xsd'),
          "gml_axis": "$(SRS_AXIS)",
          "precheck_coordsys": "$(COORD)",
          "overlap_check": "$(OVER_CHECK)",
          "overlap_tol": "$(OVERLAP)%",
          "planar_tol_angle": "$(PLAN_ANG) deg",
          "planar_tol_thickness": "$(PLAN_DIST)",
          "snal_tol": "$(TOLERANCE)",
          "solid_check_precision": "$(PREC)",
          "boundedBy_check": "$(BOUNDEDBY)"
        },
        "time": "@DateTimeNow()",
        "type": "fme_report",
        "fme version": "$(FME_BUILD_NUM)",
        "validity": xs:boolean(fme:get-attribute("_file_valid")),
        "features_overview": fme:process-features("FEATSUM"),
        "primitives_overview": fme:process-features("PRIMSUM"),
        "dataset_errors": fme:process-features("DATASET"),
        "features": fme:process-features("FEATURES")
      }
    VISIBLE_QUERY_VALIDATE = Yes
    -> JSONFormatter
Note: Make more readable
JSONFormatter
    ERROR_LIST_ATTR = _json_error
    FORMAT = Pretty Print
    INDENT_STYLE = 3 spaces
    JSON_DOCUMENT = @Value(_result)
    OUTPUT_ATTR = _formatted
    OUTPUT_ENCODING = UTF-8
    READ_FROM_FILE = NO
    REMOVE_EMPTY_OBJECTS_AND_ARRAYS = No
    REMOVE_EMPTY_STRINGS = No
    REMOVE_NULLS = No
    -> AttributeRenamer_2
AttributeRenamer_2
    ATTR_TABLE = RENAME_SET_DEFAULT _formatted > text_line_data
    -> FilenamePartExtractor_2
FilenamePartExtractor_2
    DIRNAME_ATTR = _dirname
    DIRPATH_ATTR = _dirpath
    EXTENSION_ATTR = _extension
    FULLNAME_ATTR = _filename
    ROOTNAME_ATTR = _rootname
    SRC_ATTR = $(OUTPUT)
    -> AttributeCreator_10
AttributeCreator_10
    ATTR_TABLE = SET_TO _folder = FME_CONDITIONAL:DEFAULT_VALUE'_FME_NO_OP_'BOOL_OP;OR;COMPOSITE_TEST;1;TEST @Value(_file_valid) = 0'invalid'BOOL_OP;OR;COMPOSITE_TEST;1;TEST @Value(_file_valid) = 1'valid'FME_NUM_CONDITIONS3___
    -> FeatureWriter [text_line]

Bookmark: Structure Summary
FilenamePartExtractor
    FULLNAME_ATTR = fme_dataset
    SRC_ATTR = @Value(fme_dataset)
    -> Aggregator_3
Aggregator_3
    ACCUM_ATTRS_NAME = Merge Incoming Attributes
    LIST_ATTRS_TO_INCLUDE = error_code error_level fme_dataset
    LIST_NAME = errors
    MODE = Attributes Only
    SEP = ,
    AGGREGATE -> ListCopier
ListCopier
    DEST_LIST = fme_dataset
    SRC_LIST = errors{}
    -> AttributeRemover
AttributeRemover
    LIST_ATTRS = errors{}.fme_dataset fme_dataset{}.error_code fme_dataset{}.error_level
    -> ListDuplicateRemover_3
ListDuplicateRemover_3
    SRC_LIST = fme_dataset{}.fme_dataset
    -> ListSorter
ListSorter
    ORDER = Ascending
    SRC_LIST = errors{}.error_code
    TYPE = Numeric
    -> ListDuplicateRemover_2
ListDuplicateRemover_2
    SRC_LIST = errors{}.error_code
    -> ListSearcher
ListSearcher
    ATTR_VALUE = FAIL
    INDEX_ATTR = _list_index
    LIST_ATTR = errors{}.error_level
    MATCHTYPE = FIRST_MATCHED_ENCODED
    FOUND -> AttributeCreator_24
    NOT_FOUND -> AttributeCreator_25
AttributeCreator_24
    ATTR_TABLE = SET_TO _file_valid = 0
    -> FeatureMerger_4 [REQUESTOR]
AttributeCreator_25
    ATTR_TABLE = SET_TO _file_valid = 1
    -> FeatureMerger_4 [REQUESTOR]
Tester_32
    BOOL_OP = OR
    COMPOSITE_TEST = 1
    TEST_CLAUSE = TEST error_code ATTRIBUTE_IS_MISSING ""
    TEST_MODE = TEST
    FAILED -> AttributeKeeper_5
AttributeKeeper_5
    CREATE_BULK_MODE_FEATURES = No
    KEEP_ATTRS = error_code
    -> StatisticsCalculator_3
StatisticsCalculator_3
    CALCULATION_MODE = NUMERIC
    FEAT_STATS = error_code,,,COUNT,,,,,,,,,
    GROUP_BY = error_code
    SUMMARY -> AttributeValueMapper
AttributeValueMapper
    DIRECTION = Forward (Source To Destination)
    LUT = 100,Contains NaNs, Infinities or Null Geometry Parts,102,Duplicate Consecutive Points in 2D,104,Self-Intersections in 2D,105,Degenerate or Corrupt Geometries,201,Donut: Overlapping or Touching Rings,202,Donut: Duplicate Rings,203,Non Planar Polygon: Thickness,204,Non Planar Polygon: Normal Deviation,205,Donut: Disjoint Interior,206,Donut: Hole Outside Shell,207,Donut: Nested Hole,208,Incorrect Orientation,300,Not a Valid 2-Manifold,301,Not Enough Faces,302,Surface Not Closed,305,Multiple Connected Components,306,Surface Self Intersects,307,Face Wrong Orientation,308,Surface Wrong Orientation,309,Vertices Not Used,399,Miscellaneous,401,Shells Intersect,402,Duplicate Shells,403,Inner Shell Outside Outer,404,Interior of Shell Not Connected,405,Incorrect Solid Orientation,609,Building with no Solid primitive,610,LoD2( or LoD3) Building No GroundSurface,611,LoD2( or LoD3) Building No WallSurface,612,LoD2( or LoD3) Building No RoofSurface,613,Unsupported LoD,614,Feature Overlap in 2D,617,LoD2( or LoD3) Soild contains unlinked boundedBy Surfaces,619,LoD2( or LoD3) Soild contains Invalid xlinked surface,905,Duplicate gml:id,999,Unknown Geometry Error
    SRC = error_code
    VAL_ATTR = _description
    -> Sorter_2
Sorter_2
    SORT_PARM = error_code NUMERIC ASCENDING
    SORTED -> JSONTemplater [ERRORS]
FeatureMerger_4
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> JSONTemplater [ROOT]
    UNMERGED_REQUESTOR -> JSONTemplater [ROOT]

Bookmark: Collect Features
Note: Features
Aggregator
    ACCUM_ATTRS_NAME = Drop Incoming Attributes
    CONCAT_ATTRS = error_level
    COUNT_ATTR = _num_cityobjects
    GROUP_BY = gml_id fme_feature_type
    LIST_ATTRS_TO_INCLUDE = error_code error_level
    LIST_NAME = errors
    MODE = Attributes Only
    SEP = ,
    AGGREGATE -> DuplicateFilter_5
    AGGREGATE -> AttributeCreator_23
DuplicateFilter_5
    INPUT_ORDERED_CHOICE = No
    KEYATTR = gml_id
    UNIQUE -> ListSearcher_3
ListSearcher_3
    ATTR_VALUE = FAIL
    INDEX_ATTR = _list_index
    LIST_ATTR = errors{}.error_level
    MATCHTYPE = FIRST_MATCHED_ENCODED
    FOUND -> Counter_2
    NOT_FOUND -> Counter
Counter_2
    CNT_ATTR = _failed_count
    DOMAIN = @Value(fme_feature_type)
    SCOPE = Local
    START = 1
    -> Sampler
Sampler
    GROUP_BY = fme_feature_type
    RATE = 1
    SAMPLE_MODE = No
    SAMPLE_TYPE_LONG = Last N Features
    SAMPLED -> Aggregator_5
Counter
    CNT_ATTR = _passed_count
    DOMAIN = @Value(fme_feature_type)
    SCOPE = Local
    START = 1
    -> Sampler_2
Sampler_2
    GROUP_BY = fme_feature_type
    RATE = 1
    SAMPLE_MODE = No
    SAMPLE_TYPE_LONG = Last N Features
    SAMPLED -> Aggregator_5
Aggregator_5
    ACCUM_ATTRS_NAME = Merge Incoming Attributes
    GROUP_BY = fme_feature_type
    MODE = Attributes Only
    SEP = ,
    AGGREGATE -> AttributeCreator_4
AttributeCreator_4
    ATTR_TABLE:
      SET_TO _passed_count = FME_CONDITIONAL:DEFAULT_VALUE'_FME_NO_OP_'BOOL_OP;OR;COMPOSITE_TEST;1;TEST _passed_count ATTRIBUTE_IS_MISSING _FME_BLANK_STRING_'0'FME_NUM_CONDITIONS2___
      SET_TO _failed_count = FME_CONDITIONAL:DEFAULT_VALUE'_FME_NO_OP_'BOOL_OP;OR;COMPOSITE_TEST;1;TEST _failed_count ATTRIBUTE_IS_MISSING _FME_BLANK_STRING_'0'FME_NUM_CONDITIONS2___
    -> ExpressionEvaluator_2
ExpressionEvaluator_2
    ACTION = Create New Attribute
    EXPRESSION = @Value(_failed_count)+@Value(_passed_count)
    VAL_ATTR = _num_cityobjects
    -> JSONTemplater [FEATSUM]
AttributeCreator_23
    ATTR_TABLE = SET_TO validity = FME_CONDITIONAL:DEFAULT_VALUE'1'BOOL_OP;OR;COMPOSITE_TEST;1;CASE_INSENSITIVE_TEST @Value(error_level) CONTAINS FAIL'0'BOOL_OP;OR;COMPOSITE_TEST;1;CASE_INSENSITIVE_TEST @Value(error_level) CONTAINS WARNING'1'FME_NUM_CONDITIONS3___
    -> Tester_8
Tester_8
    BOOL_OP = OR
    COMPOSITE_TEST = 1
    TEST_CLAUSE = TEST @Value(validity) = 0
    TEST_MODE = TEST
    PASSED -> ListSorter_4
ListDuplicateRemover_6
    SRC_LIST = errors{}.error_code
    -> ListSorter_2
ListSorter_2
    ORDER = Ascending
    SRC_LIST = errors{}.error_code
    TYPE = Numeric
    -> JSONTemplater [FEATURES]

Bookmark: Parse ADE file paths
Creator
    GEOMTYPE = Geometry Object
    NUM = 1
    CREATED -> ParameterFetcher_4
ParameterFetcher_4
    ATTR_LIST = _ADE_XSD_DOC $(ADE_XSD_DOC)
    -> Tester_30
Tester_30
    BOOL_OP = OR
    COMPOSITE_TEST = 1 OR 2 OR 3
    TEST_CLAUSE:
      TEST _ADE_XSD_DOC ATTRIBUTE_VALUE_NULL ""
      TEST _ADE_XSD_DOC ATTRIBUTE_IS_EMPTY ""
      TEST _ADE_XSD_DOC ATTRIBUTE_IS_MISSING ""
    TEST_MODE = TEST
    PASSED -> Aggregator_9
    FAILED -> Tester_31
Tester_31
    BOOL_OP = OR
    COMPOSITE_TEST = 1
    TEST_CLAUSE = CASE_INSENSITIVE_TEST @Value(_ADE_XSD_DOC) CONTAINS
    TEST_MODE = CASE_INSENSITIVE_TEST
    PASSED -> AttributeSplitter_5
    FAILED -> Aggregator_9
AttributeSplitter_5
    ATTR_NAME = _ADE_XSD_DOC
    DELIMITER = " "
    DROP_EMPTY_PARTS = No
    LIST_NAME = _xsd
    TRIM_OPTION = Both
    -> ListExploder_11
ListExploder_11
    ATTR_ACCUM_MODE = Merge List Attributes
    ATTR_CONFLICT_RES = Use List Attribute Values
    LIST_ATTR = _xsd{}
    ELEMENTS -> StringReplacer_3
StringReplacer_3
    CASE = NO
    FIND_TEXT = "
    NO_MATCH = _FME_NO_OP_
    REGEXP = NO
    SRC_ATTRS = _xsd
    -> DuplicateFilter_10
DuplicateFilter_10
    INPUT_ORDERED_CHOICE = No
    KEYATTR = _xsd
    UNIQUE -> Aggregator_9
Aggregator_9
    ACCUM_ATTRS_NAME = Drop Incoming Attributes
    LIST_ATTRS_TO_INCLUDE = _xsd
    LIST_NAME = _xsd
    MODE = Attributes Only
    SEP = " "
    AGGREGATE -> FeatureMerger_4 [SUPPLIER]

FME custom transformer CityGMLBuildingCollector
Aggregates CityGML features relating to buildings together.

Parameters:
- FME_FEATURE_TYPE =
- FME_PROCESS_GROUP_BY =
- GML_ID =
- GML_PARENT_ID =

Input (input)
    -> AttributeCreator_12
AttributeCreator_12
    ATTR_TABLE = SET_TO type = @Value(fme_feature_type)
    -> AttributeExposer
AttributeExposer
    ATTR_LIST = citygml_feature_role
    -> GeometryPropertySetter
GeometryPropertySetter
    GQUERY:
      for $geom in //geometry
      where $geom/count(parent::geometry) = 0
      return number($geom/@fme_id)
    OVERWRITE_CHOICE = Yes
    REMOVE_ATTRIBUTE = No
    SETTYPE_PARAM = Traits From Attributes
    SRC_ATTRS = type citygml_feature_role
    SET -> Tester_24
Tester_24
    BOOL_OP = COMPOSITE
    COMPOSITE_TEST = 1 AND 2
    TEST_CLAUSE:
      TEST @Value(fme_feature_type) IN Door,Window,WallSurface,GroundSurface,RoofSurface,ClosureSurface,OuterFloorSurface,OuterCeilingSurface
      TEST @Value(citygml_feature_role) = cityObjectMember
    TEST_MODE = TEST
    PASSED -> Rejected (output)
    FAILED -> AttributeFilter
AttributeFilter
    ATTR_NAME = fme_feature_type
    ATTR_VALUES = <Empty>,<Missing>,<Null>,<Unfiltered>,Door,Window,WallSurface,GroundSurface,RoofSurface,OuterFloorSurface,OuterCeilingSurface,ClosureSurface,TunnelInstallation,BridgeInstallation,BridgeConstructionElement,BuildingInstallation,BuildingPart,TunnelPart,BridgePart,Building,Bridge,Tunnel
    <UNFILTERED> -> Rejected (output)
    Door -> Aggregator_2
    Window -> Aggregator_2
    WallSurface -> Aggregator_7
    GroundSurface -> Aggregator_7
    RoofSurface -> Aggregator_7
    OuterFloorSurface -> Aggregator_7
    OuterCeilingSurface -> Aggregator_7
    ClosureSurface -> Aggregator_7
    TunnelInstallation -> Aggregator_8
    BridgeInstallation -> Aggregator_8
    BridgeConstructionElement -> Aggregator_8
    BuildingInstallation -> Aggregator_8
    BuildingPart -> Aggregator_9
    TunnelPart -> Aggregator_9
    BridgePart -> Aggregator_9
    Building -> Aggregator_10
    Bridge -> Aggregator_10
    Tunnel -> Aggregator_10
Rejected (output)
Aggregator_2
    ACCUM_ATTRS_NAME = Use Attributes From One Feature
    AGGREGATE_TYPE = Homogeneous Collection (If Possible)
    GROUP_BY = gml_parent_id
    MODE = Geometry - Assemble One Level
    SEP = ,
    AGGREGATE -> Tester_4
Tester_4
    BOOL_OP = OR
    COMPOSITE_TEST = 1
    TEST_CLAUSE = TEST gml_parent_id ATTRIBUTE_IS_MISSING ""
    TEST_MODE = TEST
    PASSED -> AttributeKeeper_2
    FAILED -> AttributeRenamer_2
AttributeRenamer_2
    ATTR_TABLE = RENAME_SET_DEFAULT gml_parent_id > gml_id
    -> AttributeKeeper_2
AttributeKeeper_2
    CREATE_BULK_MODE_FEATURES = No
    KEEP_ATTRS = gml_id
    -> Aggregator_7
Aggregator_7
    ACCUM_ATTRS_NAME = Use Attributes From One Feature
    AGGREGATE_TYPE = Homogeneous Collection (If Possible)
    GROUP_BY = gml_parent_id
    MODE = Geometry - Assemble One Level
    SEP = ,
    AGGREGATE -> Tester
Tester
    BOOL_OP = OR
    COMPOSITE_TEST = 1
    TEST_CLAUSE = TEST gml_parent_id ATTRIBUTE_IS_MISSING ""
    TEST_MODE = TEST
    PASSED -> AttributeKeeper_3
    FAILED -> AttributeRenamer
AttributeRenamer
    ATTR_TABLE = RENAME_SET_DEFAULT gml_parent_id > gml_id
    -> AttributeKeeper_3
AttributeKeeper_3
    CREATE_BULK_MODE_FEATURES = No
    KEEP_ATTRS = gml_id
    -> Aggregator_8
Aggregator_8
    ACCUM_ATTRS_NAME = Merge Incoming Attributes
    AGGREGATE_TYPE = Homogeneous Collection (If Possible)
    GROUP_BY = gml_id
    MODE = Geometry - Assemble One Level
    SEP = ,
    AGGREGATE -> Tester_2
Tester_2
    BOOL_OP = OR
    COMPOSITE_TEST = 1
    TEST_CLAUSE = TEST gml_parent_id ATTRIBUTE_IS_MISSING ""
    TEST_MODE = TEST
    PASSED -> AttributeKeeper_4
    FAILED -> AttributeRenamer_3
AttributeRenamer_3
    ATTR_TABLE = RENAME_SET_DEFAULT gml_parent_id > gml_id
    -> AttributeKeeper_4
AttributeKeeper_4
    CREATE_BULK_MODE_FEATURES = No
    KEEP_ATTRS = gml_id
    -> Aggregator_9
Aggregator_9
    ACCUM_ATTRS_NAME = Merge Incoming Attributes
    AGGREGATE_TYPE = Homogeneous Collection (If Possible)
    GROUP_BY = gml_id
    MODE = Geometry - Assemble One Level
    SEP = ,
    AGGREGATE -> Tester_3
Tester_3
    BOOL_OP = OR
    COMPOSITE_TEST = 1
    TEST_CLAUSE = TEST gml_parent_id ATTRIBUTE_IS_MISSING ""
    TEST_MODE = TEST
    PASSED -> AttributeKeeper_5
    FAILED -> AttributeRenamer_4
AttributeRenamer_4
    ATTR_TABLE = RENAME_SET_DEFAULT gml_parent_id > gml_id
    -> AttributeKeeper_5
AttributeKeeper_5
    CREATE_BULK_MODE_FEATURES = No
    KEEP_ATTRS = gml_id
    -> Aggregator_10
Note: Buildings
Aggregator_10
    ACCUM_ATTRS_NAME = Merge Incoming Attributes
    AGGREGATE_TYPE = Homogeneous Collection (If Possible)
    GROUP_BY = gml_id
    MODE = Geometry - Assemble One Level
    SEP = ,
    AGGREGATE -> Aggregated (output)
Aggregated (output)

FME custom transformer OverlapPercentCalculator
Calculates the 2D overlap of features

Parameters:
- GROUP_BY =
- ID =
- OVERLAP =
- SHOW_OVERLAPS =

Input (input)
    -> CoordinateSystemMapUnitExtractor
CoordinateSystemMapUnitExtractor
    -> Tester_3
Tester_3
    BOOL_OP = OR
    COMPOSITE_TEST = 1
    TEST_CLAUSE = TEST @Value(_units) = longlat
    TEST_MODE = TEST
    PASSED -> CsmapReprojector
    FAILED -> ParameterFetcher
CsmapReprojector
    DEST = EPSG:3857
    INTERPOLATION_TYPE_NAME = Nearest Neighbor
    RASTER_CELL_SIZE = Preserve Cells
    RASTER_TOLERANCE = 0.0
    VERTICAL_HANDLING = Ignore heights and leave them unchanged
    REPROJECTED -> ParameterFetcher
ParameterFetcher
    ATTR_LIST = _GROUP_BY $(GROUP_BY)
    -> 2DForcer
2DForcer
    2D -> GeometryFilter
GeometryFilter
    BREAK_AGG = No
    GEOM_PORT_NAMES = Area Ellipse
    AREA -> Bufferer
Bufferer
    ANGLE = 22.5
    CAP_STYLE = Square
    CORNER_STYLE = Arc
    MODE = AREA
    OFFSET = 0
    OFFSET_UNITS = NONE
    PRECISION = APPROX
    BUFFERED -> Dissolver
Dissolver
    ACCUM_INPUT_ATTRS = Use Attributes From One Feature
    CLEANING_TOLERANCE = 0.01
    CONNECT_Z_MODE = First Wins
    DEAGGREGATE_INPUT = Yes
    GROUP_BY = gml_id
    AREA -> AttributeCreator
AttributeCreator
    ATTR_TABLE = SET_TO original_area = yes
    -> GeometryPropertySetter
GeometryPropertySetter
    GQUERY:
      for $geom in //geometry
      where $geom/count(parent::geometry) = 0
      return number($geom/@fme_id)
    OVERWRITE_CHOICE = Yes
    REMOVE_ATTRIBUTE = Yes
    SETTYPE_PARAM = Traits From Attributes
    SRC_ATTRS = original_area
    SET -> AreaCalculator
AreaCalculator
    AREA_ATTR = _original_area
    AREA_TYPE = Plane Area
    MULT = 1
    -> AreaOnAreaOverlayer [AREA]
    -> Aggregator_2
AreaOnAreaOverlayer
    ACCUM_ATTRS_NAME = Use Attributes From One Feature
    CLEANING_TOLERANCE = Automatic
    CONNECT_Z_MODE = First Wins
    DEAGGREGATE_INPUT = Yes
    GROUP_BY = _GROUP_BY
    LIST_ATTRS_TO_INCLUDE = gml_id
    LIST_NAME = overlaps
    OVC_ATTR = _overlaps
    AREA -> Tester_5
Tester_5
    BOOL_OP = OR
    COMPOSITE_TEST = 1
    TEST_CLAUSE = TEST @Value(_overlaps) > 1
    TEST_MODE = TEST
    PASSED -> ExpressionEvaluator_2
ExpressionEvaluator_2
    ACTION = Create New Attribute
    EXPRESSION = @Value(_overlaps)-1
    VAL_ATTR = _overlaps
    -> ListSearcher
ListSearcher
    ATTR_VALUE = @Value(gml_id)
    INDEX_ATTR = _list_index
    LIST_ATTR = overlaps{}.gml_id
    MATCHTYPE = FIRST_MATCHED_ENCODED
    FOUND -> ListExploder_3
ListExploder_3
    ATTR_ACCUM_MODE = Merge List Attributes
    ATTR_CONFLICT_RES = Use List Attribute Values
    LIST_ATTR = overlaps{}
    ELEMENTS -> Aggregator_2
Aggregator_2
    ACCUM_ATTRS_NAME = Merge Incoming Attributes
    AGGREGATE_TYPE = Homogeneous Collection (If Possible)
    GROUP_BY = gml_id _GROUP_BY
    MODE = Geometry - Assemble One Level
    SEP = ,
    SUM = _overlaps
    AGGREGATE -> AreaCalculator_3
AreaCalculator_3
    AREA_ATTR = _area
    AREA_TYPE = Plane Area
    MULT = 1
    -> ExpressionEvaluator
ExpressionEvaluator
    ACTION = Create New Attribute
    EXPRESSION = (@Value(_area)/@Value(_original_area)-1)*100
    VAL_ATTR = _overlap_percentage
    -> Tester_4
Tester_4
    BOOL_OP = OR
    COMPOSITE_TEST = 1
    TEST_CLAUSE = TEST @Value(_units) = longlat
    TEST_MODE = TEST
    PASSED -> CsmapReprojector_2
    FAILED -> TestFilter_2
CsmapReprojector_2
    DEST = @Value(_coordsys)
    INTERPOLATION_TYPE_NAME = Nearest Neighbor
    RASTER_CELL_SIZE = Preserve Cells
    RASTER_TOLERANCE = 0.0
    VERTICAL_HANDLING = Ignore heights and leave them unchanged
    REPROJECTED -> TestFilter_2
TestFilter_2
    DEFAULT_VALUE = <UNFILTERED>
    TEST_LIST = "BOOL_OP,OR,COMPOSITE_TEST,""""""1"""""",TEST_CLAUSE,TEST @Value(_overlap_percentage) > $(OVERLAP)",FAIL,"BOOL_OP,OR,COMPOSITE_TEST,""""""1"""""",TEST_CLAUSE,NUM_TEST @Value(_overlap_percentage) RANGE (0,@Evaluate($(OVERLAP))]",PASS,"BOOL_OP,OR,COMPOSITE_TEST,""""""1"""""",TEST_CLAUSE,TEST @Value(_overlap_percentage) = 0",NO_OVERLAP
    FAIL -> Tester
    PASS -> Tester_2
    NO_OVERLAP -> GeometryPartExtractor_2
Tester
    BOOL_OP = OR
    COMPOSITE_TEST = 1
    TEST_CLAUSE = TEST $(SHOW_OVERLAPS) = Yes
    TEST_MODE = TEST
    PASSED -> FAIL (output)
    FAILED -> GeometryPartExtractor_3
GeometryPartExtractor_3
    GQUERY:
      for $geom in //geometry
      where fme:trait-equals(fme:get-trait($geom, 'original_area'), 'yes')
      return number($geom/@fme_id)
    EXTRACTED -> FAIL (output)
FAIL (output)
Tester_2
    BOOL_OP = OR
    COMPOSITE_TEST = 1
    TEST_CLAUSE = TEST $(SHOW_OVERLAPS) = Yes
    TEST_MODE = TEST
    PASSED -> PASS (output)
    FAILED -> GeometryPartExtractor
GeometryPartExtractor
    GQUERY:
      for $geom in //geometry
      where fme:trait-equals(fme:get-trait($geom, 'original_area'), 'yes')
      return number($geom/@fme_id)
    EXTRACTED -> PASS (output)
PASS (output)
GeometryPartExtractor_2
    GQUERY:
      for $geom in //geometry
      where fme:trait-equals(fme:get-trait($geom, 'original_area'), 'yes')
      return number($geom/@fme_id)
    EXTRACTED -> NO_OVERLAP (output)
NO_OVERLAP (output)

FME custom transformer CoordinateSystemMapUnitExtractor
Extracts the map units from the defined coordinate system of the entering features.
Outputs:
_units: This feature's defined map unit.
eg. 'latlong' for degrees, 'm' for meters, 'ft' or 'us-ft' for feet.

Input (input)
    -> CoordinateSystemExtractor
CoordinateSystemExtractor
    CRDSYS_ATTR = _coordsys
    -> CoordinateSystemDescriptionConverter
CoordinateSystemDescriptionConverter
    DIRECTION_LONG = Convert From FME Representation
    KIND_LONG = PROJ.4 String
    SRC = _coordsys
    VAL_ATTR = _proj4_str
    -> StringSearcher_2
StringSearcher_2
    CASE = no
    MATCHED_RESULT_ATTR = _units
    REGEXP = (?<=proj=).*?(?=\s)
    STRING_TO_SEARCH = @Value(_proj4_str)
    MATCHED -> Tester
Tester
    BOOL_OP = OR
    COMPOSITE_TEST = 1
    TEST_CLAUSE = TEST @Value(_units) = longlat
    TEST_MODE = TEST
    PASSED -> Output (output)
    FAILED -> StringSearcher
StringSearcher
    CASE = no
    MATCHED_RESULT_ATTR = _units
    REGEXP = (?<=units=).*?(?=\s)
    STRING_TO_SEARCH = @Value(_proj4_str)
    MATCHED -> Output (output)
Output (output)
