FME workspace runner.fmw

Parameters:
- INPUT = Sample\Sample.zip   # Source Zip File
- ADE_XSD_DOC =   # Additional ADE Schema File(s)
- SRS_AXIS = 2,1,3   # 1,2,3 | long,lat,z | x,y,z,1,2,3%2,1,3 | lat,long,z | y,x,z ,2,1,3 GML SRS Axis Order
- COORD = EPSG:6677   # EnableReadFromFeature:No Pre Validaion Coordinate System (projected)
- OVER_CHECK = ALL   # Perform (2D) Building overlap check?
- OVERLAP = 5   # Amount of allowed overlap (%)
- TOLERANCE = 0.001   # Snapping tolerance (distance units)
- BOUNDEDBY = No   # Check presence of mandatory boundedBy surfaces in Buildings and Building Parts (610,611,612)
- PREC = 3   # Coordinate Precision for solid boundary checks
- PLAN_ANG = 20   # Planar surface tolerance based on normal deviation (degrees)
- PLAN_DIST = 0.03   # Planar surface tolerance based on distance ('thickness' of plane)
- OUTPUT = OutputFolder   # Destination json report folder
- MAX_PROC = 7   # Maximum Number of Concurrent Processes (1-7)
- WORKSPACE_FILE = CityGMLValidation.fmw   # CityGMLValidation path
- LOG = logs   # Choose output logfile folder

Note: Run jobs in parallel
WorkspaceRunner
    BLOCKING = No
    MAX_PROC = $(MAX_PROC)
    MAX_TO_BATCH = 7
    WORKSPACE_FILE = $(WORKSPACE_FILE)
    WORKSPACE_PARAMETERS = INPUT,@Value(path_windows),ADE_XSD_DOC,$(ADE_XSD_DOC),SRS_AXIS,$(SRS_AXIS),COORD,$(COORD),OVER_CHECK,$(OVER_CHECK),OVERLAP,$(OVERLAP),TOLERANCE,$(TOLERANCE),BOUNDEDBY,$(BOUNDEDBY),PREC,$(PREC),PLAN_ANG,$(PLAN_ANG),PLAN_DIST,$(PLAN_DIST),OUTPUT,$(OUTPUT)\@Value(_rootname).json,LOG_FILE,$(LOG)\@Value(_rootname).log
    SUCCEEDED -> Logger
    FAILED -> Logger_3
    SUMMARY -> Logger_2
Logger
    LOG_FEATURE = NONE
    MAXFEATS = 99999
    MESSAGE = submitted @Value(_filename) for validation
    SEVERITY = INFO
Logger_3
    LOG_FEATURE = NONE
    MAXFEATS = 99999
    MESSAGE = failed to submit @Value(_filename) for validation
    SEVERITY = INFO
Logger_2
    LOG_FEATURE = NONE
    MAXFEATS = 1
    MESSAGE = Final jobs submitted, waiting for completion
    SEVERITY = INFO
    LOGGED -> PythonCaller
Note: Wait until last process is finished
PythonCaller
    PYTHONSOURCE:
      #credit to fme user simon_maddern for the python code wihch can be found here https://community.safe.com/s/idea/0874Q000000Tko5QAC/detail

      import fme
      import fmeobjects
      import subprocess
      import re
      import time

      pattern = re.compile(r"fme[A-Z]*\.exe {1,}([0-9]{1,})")
      wait_secs = 15

      class FeatureProcessor(object):
          def __init__(self):
              pass
          def check_tasks_running(self, processes):
              tasks_running = False
              for task in subprocess.check_output("tasklist").splitlines():
                  match = pattern.search(str(task))
                  if match:
                      if match.group(1) in processes:
                          tasks_running = True
              if tasks_running:
                  return False
                  time.sleep(wait_secs)
              else:
                  return True
          def input(self,feature):
              processes = feature.getAttribute('_processes')
              jobs_finished = False
              while not jobs_finished:
                  jobs_finished = self.check_tasks_running(processes)
              self.pyoutput(feature)
          def close(self):
              pass
    PYTHONSYMBOL = FeatureProcessor

Bookmark: Build List of input files
Creator_2
    GEOMTYPE = Geometry Object
    NUM = 1
    CREATED -> ParameterFetcher_4
ParameterFetcher_4
    ATTR_LIST = _INPUT $(INPUT)
    -> Tester
Tester
    BOOL_OP = OR
    COMPOSITE_TEST = 1
    TEST_CLAUSE = CASE_INSENSITIVE_TEST $(INPUT) CONTAINS .zip
    TEST_MODE = TEST
    PASSED -> Unzipper
    FAILED -> Tester_31
Tester_31
    BOOL_OP = OR
    COMPOSITE_TEST = 1
    TEST_CLAUSE = CASE_INSENSITIVE_TEST @Value(_INPUT) CONTAINS
    TEST_MODE = CASE_INSENSITIVE_TEST
    PASSED -> AttributeSplitter_5
    FAILED -> AttributeRenamer
AttributeSplitter_5
    ATTR_NAME = _INPUT
    DELIMITER = " "
    DROP_EMPTY_PARTS = No
    LIST_NAME = _input
    TRIM_OPTION = Both
    -> ListExploder_11
ListExploder_11
    ATTR_ACCUM_MODE = Merge List Attributes
    ATTR_CONFLICT_RES = Use List Attribute Values
    LIST_ATTR = _input{}
    ELEMENTS -> StringReplacer_3
StringReplacer_3
    CASE = NO
    FIND_TEXT = "
    NO_MATCH = _FME_NO_OP_
    REGEXP = NO
    SRC_ATTRS = _input
    -> Junction
AttributeRenamer
    ATTR_TABLE = RENAME_SET_DEFAULT _INPUT > _input
    -> Junction
Junction
    -> AttributeRenamer_2
AttributeRenamer_2
    ATTR_TABLE = RENAME_SET_DEFAULT _input > path_windows
    -> Tester_2
Tester_2
    BOOL_OP = OR
    COMPOSITE_TEST = 1
    TEST_CLAUSE = CASE_INSENSITIVE_TEST @Value(path_windows) CONTAINS *
    TEST_MODE = TEST
    PASSED -> FilenamePartExtractor_2
    FAILED -> FilenamePartExtractor
FilenamePartExtractor_2
    DIRNAME_ATTR = _dirname
    DIRPATH_ATTR = _dirpath
    EXTENSION_ATTR = _extension
    FULLNAME_ATTR = _filename
    ROOTNAME_ATTR = _rootname
    SRC_ATTR = @Value(path_windows)
    -> FeatureReader [INITIATOR]
FeatureReader
    ATTR_ACCUM_MODE = Only Use Result
    COMBINE_GEOM = Use Result
    DATASET = @Value(_dirpath)
    FORMAT = PATH
    OUTPUT_FEATURES_DISPLAY = Schema and Data Features
    PATH_GLOB_PATTERN = @Value(_filename)
    PATH_NO_EMPTY_PROPERTIES = YES
    PATH_RECURSE_DIRECTORIES = NO
    PATH_RETRIEVE_FILE_PROPERTIES = NO
    PATH_TYPE = FILE
    <OTHER> -> FilenamePartExtractor
Note: If import is a zip then unzip
Unzipper
    ZIPFILE_PATH = $(INPUT)
    -> Tester_3
Tester_3
    BOOL_OP = OR
    COMPOSITE_TEST = 1 OR 2
    TEST_CLAUSE:
      CASE_INSENSITIVE_TEST @Value(path_windows) ENDS_WITH .gml
      CASE_INSENSITIVE_TEST @Value(path_windows) ENDS_WITH .xml
    TEST_MODE = TEST
    PASSED -> FilenamePartExtractor
FilenamePartExtractor
    DIRNAME_ATTR = _dirname
    DIRPATH_ATTR = _dirpath
    EXTENSION_ATTR = _extension
    FULLNAME_ATTR = _filename
    ROOTNAME_ATTR = _rootname
    SRC_ATTR = @Value(path_windows)
    -> WorkspaceRunner

FME custom transformer Unzipper
Description
This transformer extracts a zip file to a temporary directory, returning the path in both Windows- and Unix-style. Using these paths, you can copy the files to a permanent location using a File Copy writer, or make further use of them in a FeatureReader, for example. 
Details
This custom transformer utilizes a FeatureReader with the Directory and File Pathnames format to extract the files within the input zip dataset to a temporary location. 
One feature for each file contained within the zip dataset is sent through the Output port with the attribute path_windows and path_unix containing the Windows- and Unix-style temporary file path respectively.
Input Port
This port accepts any feature. Each feature is expected to have as attribute the path to a zipfile.
Output Port
Will output a feature for each file inside the zipfile. Each feature will have a path_windows and path_unix attribute, with backslashes and forward slashes respectively.
 Port
Upon unzipping error, outputs the original Initiator feature with the addition of the _reader_error attribute which contains the last error message from the transformer.
Parameters
Zipfile path: The path to a zipfile from which you would like to extract files. This can be set to an attribute or a file on the system. Please note that if you specify a file directly, its contents will be extracted once for every initiator feature that enters the transformer.
Usage notes
The files will be extracted to a temporary location, so if you would like to save them, you would need to use a File Copy writer to write them out to a permanent location.

Parameters:
- ZIPFILE_PATH =   # Zipfile path

Input (input)
    -> ParameterFetcher
Note: Fetch path of zip file from input parameter and create attribute
ParameterFetcher
    ATTR_LIST = _unzipper_zipfile_path {$(ZIPFILE_PATH)}
    -> FeatureReader [INITIATOR]
Note: Gets listing of zip file contents / (extraction is performed automatically / to temp location)
FeatureReader
    ATTRIBUTES = PATH,"path_unix,path_windows,path_rootname,path_filename,path_extension,path_filesize,path_ownername,path_readonly,path_modified_date,path_created_date,path_accessed_date,path_directory_unix,path_directory_windows,path_type,fme_geometry{0}"
    ATTR_ACCUM_MODE = Only Use Result
    COMBINE_GEOM = Use Result
    DATASET = @Value(_unzipper_zipfile_path)/**/
    FEATURETYPES = PATH
    FORMAT = PATH
    OUTPUT_FEATURES_DISPLAY = Schema and Data Features
    PATH_GLOB_PATTERN = *
    PATH_RETRIEVE_FILE_PROPERTIES = NO
    PATH_TYPE = ANY
    SUPPORTED_SPATIAL_INTERACTIONS = ENVELOPE_INTERSECT%INTERSECTS%CONTAINS%CROSSES%DISJOINT%EQUALS%OVERLAPS%TOUCHES%WITHIN
    PATH -> Output (output)
    <REJECTED> -> <Rejected> (output)
Output (output)
<Rejected> (output)
